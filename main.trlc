package vanillaEg

Requirement make_sum {
  desc = "Some requirements text, eg. this function must do a sum"
}

OutputRequirement value_int {
  desc = "Return value from function must return an integer value"
  lobster_trace = 17044
}

OutputRequirement value_decimal {
  desc = "Return value from function must return a decimal value"
  more_description = "Minimum two decimal places"
}
